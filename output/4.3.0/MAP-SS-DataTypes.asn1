-- MODULE 'MAP-SS-DataTypes' START
MAP-SS-DataTypes {
   ccitt identified-organization (4) etsi (0) mobileDomainId (0)
   gsmNetworkId(1) moduleId (3) map-SS-DataTypes (14) version2 (2)}

DEFINITIONS

IMPLICIT TAGS

::=

BEGIN

EXPORTS
	RegisterSS-Arg,
--<B--	NoReplyConditionTime,--B>--
	SS-Info,
	SS-Status,
--<B--	CUG-Index,--B>--
	CUG-Interlock,
	SS-SubscriptionOption,
	SS-ForBS-Code,
	InterrogateSS-Res,
	SS-UserData,
	ProcessSS-RequestArg,
	SS-DigitString,
	ToneOrDisplay,
	SS-GetDigitsArg,
	SS-GetStringArg,
	SS-GetStringRes,
	Password,
	GuidanceInfo,
	BeginSubscriberActivityArg,
	SS-List,
	SS-InfoList,
--<B--	SS-DataList,--B>--
	ForwardingData
;

IMPORTS
	AddressString,
	ISDN-AddressString,
	ISDN-SubaddressString,
	maxSignalInfoLength,
	IMSI,
	IMEI,
	BasicServiceCode,
	BasicServiceGroupList,
	maxNumOfBasicServiceGroups
FROM MAP-CommonDataTypes {
   ccitt identified-organization (4) etsi (0) mobileDomainId (0)
   gsmNetworkId(1) moduleId (3) map-CommonDataTypes (18) version2 (2)}

	SS-Code
FROM MAP-SS-Code {
   ccitt identified-organization (4) etsi (0) mobileDomainId (0)
   gsmNetworkId(1) moduleId (3) map-SS-Code (15) version2 (2)}
;


RegisterSS-Arg ::= SEQUENCE{
	ss-Code		SS-Code,
	basicService	BasicServiceCode	OPTIONAL,
	forwardedToNumber	[4] AddressString	OPTIONAL,
	forwardedToSubaddress	[6] ISDN-SubaddressString	OPTIONAL,
	-- OA1 forwardedToSubaddress must be absent in version 1
	noReplyConditionTime	[5] NoReplyConditionTime	OPTIONAL}

NoReplyConditionTime ::= INTEGER (5..30)

SS-Info ::= CHOICE {
	forwardingInfo	[0] ForwardingInfo,
	callBarringInfo	[1] CallBarringInfo,
	cug-Info	[2] CUG-Info,
	ss-Data		[3] SS-Data}

ForwardingInfo ::= SEQUENCE {
	ss-Code		SS-Code		OPTIONAL,
	forwardingFeatureList	ForwardingFeatureList}

ForwardingFeatureList ::= SEQUENCE SIZE (1..maxNumOfBasicServiceGroups) OF
				ForwardingFeature

ForwardingFeature ::= SEQUENCE {
	basicService	BasicServiceCode	OPTIONAL,
	ss-Status	[4] SS-Status	OPTIONAL,
	-- OP1 ss-Status must be present in version 1
	forwardedToNumber	[5] ISDN-AddressString	OPTIONAL,
	forwardedToSubaddress	[8] ISDN-SubaddressString	OPTIONAL,
	-- OA1 forwardedToSubaddress must be absent in version 1
	forwardingOptions	[6] ForwardingOptions	OPTIONAL,
	noReplyConditionTime	[7] NoReplyConditionTime	OPTIONAL}

SS-Status ::= OCTET STRING (SIZE (1))

	-- bits 8765: 0000 (unused)

	-- bit 4: quiescent/operative indicator (only if bit 1 = 1)
	--	0  operative
	--	1  quiescent

	-- bit 3: provision indicator
	--	0  not provisioned
	--	1  provisioned

	-- bit 2: registration indicator (if applicable)
	--	0  not registered
	--	1  registered

	-- bit 1: activation indicator (if applicable)
	--	0  not active
	--	1  active

ForwardingOptions ::= OCTET STRING (SIZE (1))

	-- v1: bits 87: notification to forwarding party
	--	00  no notification
	--	01  notification
	--	10  notification

	-- v2: bit 8: notification to forwarding party
	--	0  no notification
	--	1  notification

	-- v2: bit 7: 0 (unused)

	-- v1: bits 65: notification to calling party
	--	00  no notification
	--	01  notification
	--	10  notification

	-- v2: bit 6: v2: notification to calling party
	--	0  no notification
	--	1  notification

	-- v2: bit 5: 0 (unused)

	-- v2: bits 43: forwarding reason
	--	00  ms not reachable
	--	01  ms busy
	--	10  no reply
	--	11  unconditional
	-- bits 21: 00 (unused)

CallBarringInfo ::= SEQUENCE {
	ss-Code		SS-Code		OPTIONAL,
	-- OP1 ss-Code must be present in version 1
	callBarringFeatureList	CallBarringFeatureList}

CallBarringFeatureList ::= SEQUENCE SIZE (1..maxNumOfBasicServiceGroups) OF
				CallBarringFeature

CallBarringFeature ::= SEQUENCE {
	basicService	BasicServiceCode	OPTIONAL,
	ss-Status	[4] SS-Status	OPTIONAL}
	-- OP1 ss-Status must be present in version 1

CUG-Info ::= SEQUENCE {
	cug-SubscriptionList	CUG-SubscriptionList,
	cug-FeatureList	CUG-FeatureList	OPTIONAL}

CUG-SubscriptionList ::= SEQUENCE SIZE (1..maxNumOfCUG) OF
				CUG-Subscription

CUG-Subscription ::= SEQUENCE {
	cug-Index	CUG-Index,
	cug-Interlock	CUG-Interlock,
	intraCUG-Options	IntraCUG-Options,
	basicServiceGroupList	BasicServiceGroupList	OPTIONAL}

CUG-Index ::= INTEGER (0..32767)
	-- The internal structure is defined in TS ETS 300 138:1991.

CUG-Interlock ::= OCTET STRING (SIZE (4))

IntraCUG-Options ::= ENUMERATED {
	noCUG-Restrictions  (0),
	cugIC-CallBarred  (1),
	cugOG-CallBarred  (2)}

maxNumOfCUG  INTEGER ::= 10

CUG-FeatureList ::= SEQUENCE SIZE (1..maxNumOfBasicServiceGroups) OF
				CUG-Feature

CUG-Feature ::= SEQUENCE {
	basicService	BasicServiceCode	OPTIONAL,
	preferentialCUG-Indicator	CUG-Index	OPTIONAL,
	interCUG-Restrictions	InterCUG-Restrictions}

InterCUG-Restrictions::= OCTET STRING (SIZE (1))

	-- bits 876543: 000000 (unused)

	-- bits 21 
	--	00  CUG only facilities
	--	01  CUG with outgoing access
	--	10  CUG with incoming access
	--	11  CUG with both outgoing and incoming access

SS-Data ::= SEQUENCE {
	ss-Code	SS-Code,
	ss-Status	[4] SS-Status	OPTIONAL,
	ss-SubscriptionOption	SS-SubscriptionOption	OPTIONAL,
	-- OA1 ss-SubscriptionOption must be absent in version 1
	basicServiceGroupList	BasicServiceGroupList	OPTIONAL}
	-- OA1 basicServiceGroupList must be absent in version 1

SS-SubscriptionOption ::= CHOICE {
	restrictionPerCall	[5] BOOLEAN,
	overrideCategory	[1] OverrideCategory}

OverrideCategory ::= ENUMERATED {
	overrideEnabled  (0),
	overrideDisabled  (1)}

SS-ForBS-Code ::= SEQUENCE {
	ss-Code		SS-Code,
	basicService	BasicServiceCode	OPTIONAL}

InterrogateSS-Res ::= CHOICE {
	ss-Status	[0] SS-Status,
	forwardedToNumber	[1] ISDN-AddressString,
	-- NU>1 forwardedToNumber must not be used in version greater 1
	basicServiceGroupList	[2] BasicServiceGroupList,
	forwardingFeatureList	[3] ForwardingFeatureList}

SS-UserData ::= IA5String (SIZE (1.. maxSignalInfoLength))

ProcessSS-RequestArg ::= SEQUENCE {
	ss-featureAccessCode	SS-FeatureAccessCode,
	equipmentType	EquipmentType	OPTIONAL,
	ss-specificInfo	SS-SpecificInfo	OPTIONAL}

SS-FeatureAccessCode ::= OCTET STRING (SIZE (1..2))

EquipmentType ::= SEQUENCE {
	displayDeviceExists	NULL		OPTIONAL,
	imei		IMEI}

SS-SpecificInfo ::= CHOICE {
	ss-unstructuredInfo	[1] SS-UnstructuredInfo,
	ss-digitString	[2] SS-DigitString}

SS-UnstructuredInfo ::= OCTET STRING (SIZE (1..32))

SS-DigitString ::= IA5String
	(FROM ("0"|"1"|"2"|"3"|"4"|"5"|"6"|"7"|"8"|"9"|"*"|"#")|--)
	--(--SIZE (1..maxNumOfDigits))

ToneOrDisplay ::= CHOICE {
	nonRegisteredDisplay	[0] SS-DisplayString,
	preRegisteredDisplay	[1] SS-StringReference,
	tone		[2] Tone}

SS-DisplayString ::= PrintableString (SIZE (1..32))

SS-StringReference ::= INTEGER (1..127)

Tone ::= INTEGER (1..127)

SS-GetDigitsArg ::= SEQUENCE {
	toneOrDisplay	ToneOrDisplay,
	numberOfDigits	NumberOfDigits	OPTIONAL}

NumberOfDigits ::= INTEGER (1..maxNumOfDigits)

maxNumOfDigits  INTEGER ::= 20

SS-GetStringArg ::= SEQUENCE {
	toneOrDisplay	ToneOrDisplay,
	stringLength	StringLength	OPTIONAL}

StringLength ::= INTEGER (1..maxStringLength)

maxStringLength  INTEGER ::= 200

SS-GetStringRes ::= PrintableString(SIZE (1..maxStringLength))

Password ::= NumericString
	(FROM ("0"|"1"|"2"|"3"|"4"|"5"|"6"|"7"|"8"|"9")|--)
	--(--SIZE (4))

GuidanceInfo ::= ENUMERATED {
	enterPW  (0),
	enterNewPW  (1),
	enterNewPW-Again  (2)}
	-- How this information is really delivered to the subscriber
	-- (display, announcement, ...) is not part of this
	-- specification.

BeginSubscriberActivityArg ::= SEQUENCE {
	imsi		IMSI,
	originatingEntityNumber	ISDN-AddressString}

SS-List ::= SEQUENCE SIZE (1..maxNumOfSS) OF
				SS-Code

maxNumOfSS  INTEGER ::= 30

SS-InfoList ::= SEQUENCE SIZE (1..maxNumOfSS) OF
				SS-Info

--<B--SS-DataList ::= SEQUENCE SIZE (1..maxNumOfSS) OF--B>--
--<B--				SS-Data--B>--

ForwardingData ::= SEQUENCE {
	forwardedToNumber	[5] ISDN-AddressString	OPTIONAL,
	-- OP1 forwardedToNumber must be present in version 1 
	forwardedToSubaddress	[4] ISDN-SubaddressString	OPTIONAL,
	-- OA1 forwardedToSubaddress must be absent in version 1
	forwardingOptions	[6] ForwardingOptions	OPTIONAL}


END
-- MODULE END
