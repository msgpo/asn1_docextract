-- MODULE 'MAP-SS-Code' START
MAP-SS-Code {
   ccitt identified-organization (4) etsi (0) mobileDomainId (0)
   gsmNetworkId(1) moduleId (3) map-SS-Code (15) version2 (2)}

DEFINITIONS

::=

BEGIN

SS-Code ::= OCTET STRING (SIZE (1))
	-- This type is used to represent the code identifying a single
	-- supplementary service, a group of supplementary services, or
	-- all supplementary services. The services and abbreviations
	-- used are defined in GSM02.04. The internal structure is
	-- defined as follows:

	-- bits 87654321: group (bits 8765), and specific service
	-- (bits 4321)

allSS			SS-Code ::= '00000000'B
	-- all SS

allLineIdentificationSS	SS-Code ::= '00010000'B
	-- all line identification SS
clip			SS-Code ::= '00010001'B
	-- calling line identification presentation
clir			SS-Code ::= '00010010'B
	-- calling line identification restriction
colp			SS-Code ::= '00010011'B
	-- connected line identification presentation
colr			SS-Code ::= '00010100'B
	-- connected line identification restriction
mci			SS-Code ::= '00010101'B
	-- malicious call identification

allForwardingSS	SS-Code ::= '00100000'B
	-- all forwarding SS
cfu			SS-Code ::= '00100001'B
	-- call forwarding unconditional
allCondForwardingSS	SS-Code ::= '00101000'B
	-- all conditional forwarding SS
cfb			SS-Code ::= '00101001'B
	-- call forwarding on mobile subscriber busy
cfnry			SS-Code ::= '00101010'B
	-- call forwarding on no reply
cfnrc			SS-Code ::= '00101011'B
	-- call forwarding on mobile subscriber not reachable

allCallOfferingSS	SS-Code ::= '00110000'B
	-- all call offering SS includes also all forwarding SS
ct				SS-Code ::= '00110001'B
	-- call transfer
mah			SS-Code ::= '00110010'B
	-- mobile access hunting

allCallCompletionSS	SS-Code ::= '01000000'B
	-- all Call completion SS
cw				SS-Code ::= '01000001'B
	-- call waiting
hold			SS-Code ::= '01000010'B
	-- call hold
ccbs			SS-Code ::= '01000011'B
	-- completion of call to busy subscribers

allMultiPartySS	SS-Code ::= '01010000'B
	-- all multi-party SS
multiPTY		SS-Code ::= '01010001'B
	-- multi party

allCommunityOfInterest-SS	SS-Code ::= '01100000'B
	-- all community of interest SS
cug			SS-Code ::= '01100001'B
	-- closed user group

allChargingSS	SS-Code ::= '01110000'B
	-- all charging SS
aoci			SS-Code ::= '01110001'B
	-- advice of charge information
aocc			SS-Code ::= '01110010'B
	-- advice of charge charging

allAdditionalInfoTransferSS	SS-Code ::= '10000000'B
	-- all additional information transfer SS
uus			SS-Code ::= '10000001'B
	-- UUS user to user signalling

allCallRestrictionSS	SS-Code ::= '10010000'B
	-- all call restriction SS
barringOfOutgoingCalls	SS-Code ::= '10010001'B
	-- barring of outgoing calls
baoc			SS-Code ::= '10010010'B
	-- barring of all outgoing calls
boic			SS-Code ::= '10010011'B
	-- barring of outgoing international calls
boicExHC		SS-Code ::= '10010100'B
	-- barring of outgoing international calls except those directed
	-- to the home PLMN
barringOfIncomingCalls	SS-Code ::= '10011001'B
	-- barring of incoming calls
baic			SS-Code ::= '10011010'B
	-- barring of all incoming calls
bicRoam			SS-Code ::= '10011011'B
	-- barring of incoming calls when roaming outside home PLMN
	-- Country

allPLMN-specificSS	SS-Code ::= '11110000'B
-- NU1 *plmn-specific* must not be used in version 1
plmn-specificSS-1	SS-Code ::= '11110001'B
plmn-specificSS-2	SS-Code ::= '11110010'B
plmn-specificSS-3	SS-Code ::= '11110011'B
plmn-specificSS-4	SS-Code ::= '11110100'B
plmn-specificSS-5	SS-Code ::= '11110101'B
plmn-specificSS-6	SS-Code ::= '11110110'B
plmn-specificSS-7	SS-Code ::= '11110111'B
plmn-specificSS-8	SS-Code ::= '11111000'B
plmn-specificSS-9	SS-Code ::= '11111001'B
plmn-specificSS-A	SS-Code ::= '11111010'B
plmn-specificSS-B	SS-Code ::= '11111011'B
plmn-specificSS-C	SS-Code ::= '11111100'B
plmn-specificSS-D	SS-Code ::= '11111101'B
plmn-specificSS-E	SS-Code ::= '11111110'B
plmn-specificSS-F	SS-Code ::= '11111111'B


END
-- MODULE END
