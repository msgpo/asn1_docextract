-- MODULE 'MAP-OM-DataTypes' START
MAP-OM-DataTypes {
   ccitt identified-organization (4) etsi (0) mobileDomainId (0)
   gsmNetworkId(1) moduleId (3) map-OM-DataTypes (12) version2 (2)}

DEFINITIONS

IMPLICIT TAGS

::=

BEGIN

EXPORTS
	ActivateTraceModeArg,
	DeactivateTraceModeArg,
	TraceSubscriberActivityArg,
	NoteInternalHO-Arg
;

IMPORTS
	AddressString,
	ExternalSignalInfo,
	IMSI,
	GlobalCellId
FROM MAP-CommonDataTypes {
   ccitt identified-organization (4) etsi (0) mobileDomainId (0)
   gsmNetworkId(1) moduleId (3) map-CommonDataTypes (18) version2 (2)}

	IMSI-OrIMEI
FROM MAP-MS-DataTypes {
   ccitt identified-organization (4) etsi (0) mobileDomainId (0)
   gsmNetworkId(1) moduleId (3) map-MS-DataTypes (11) version2 (2)}
;


ActivateTraceModeArg ::= SEQUENCE {
	imsi		[0] IMSI	OPTIONAL,
	traceReference	[1] TraceReference,
	traceType	[2] TraceType,
	omc-Id		[3] AddressString	OPTIONAL}

TraceReference ::= OCTET STRING (SIZE (1..2))

TraceType ::= INTEGER
	(0..255)
	-- Trace types are more fully defined in TS GSM 12.02.

DeactivateTraceModeArg ::= SEQUENCE {
	imsi		[0] IMSI	OPTIONAL,
	traceReference	[1] TraceReference}

TraceSubscriberActivityArg ::= SEQUENCE {
	imsi-OrIMEI	[0] IMSI-OrIMEI	OPTIONAL,
	traceReference	[1] TraceReference,
	traceType	[2] TraceType,
	omc-Id		[3] AddressString	OPTIONAL,
	callReference	[4] CallReference	OPTIONAL}

CallReference ::= OCTET STRING (SIZE (1..3))

NoteInternalHO-Arg ::= SEQUENCE {
	handoverType	HandoverType,
	targetCellId	[1] GlobalCellId	OPTIONAL,
	channelId	[2] ExternalSignalInfo	OPTIONAL}

HandoverType ::= ENUMERATED {
	interBSS  (0),
	intraBSS  (1)}


END
-- MODULE END
