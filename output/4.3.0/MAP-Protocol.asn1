-- MODULE 'MAP-Protocol' START
MAP-Protocol {
   ccitt identified-organization (4) etsi (0) mobileDomainId (0)
   gsmNetworkId(1) moduleId (3) map-Protocol (4) version2 (2)}

DEFINITIONS

::=

BEGIN

IMPORTS
--<B--	UpdateLocationArea,--B>--
	UpdateLocation,
	CancelLocation,
	PurgeMS,
	SendIdentification,
--<B--	DetachIMSI,--B>--
--<B--	AttachIMSI,--B>--
--<B--	Page,--B>--
--<B--	SearchForMS,--B>--
--<B--	ProcessAccessRequest,--B>--
	PerformHandover,
	SendEndSignal,
	ProcessAccessSignalling,
	ForwardAccessSignalling,
	PerformSubsequentHandover,
--<B--	AllocateHandoverNumber,--B>--
--<B--	SendHandoverReport,--B>--
--<B--	Authenticate,--B>--
	SendAuthenticationInfo,
--<B--	SetCipheringMode,--B>--
	CheckIMEI,
--<B--	ObtainIMEI,--B>--
	SendParameters,
	InsertSubscriberData,
	DeleteSubscriberData,
--<B--	ProvideIMSI,--B>--
--<B--	ForwardNewTMSI,--B>--
	Reset,
	ForwardCheckSS-Indication,
	RestoreData
FROM MAP-MobileServiceOperations {
   ccitt identified-organization (4) etsi (0) mobileDomainId (0)
   gsmNetworkId(1) moduleId (3) map-MobileServiceOperations (5)
   version2 (2)}

	ActivateTraceMode,
	DeactivateTraceMode,
	TraceSubscriberActivity,
	NoteInternalHandover,
	SendIMSI
FROM MAP-OperationAndMaintenanceOperations {
   ccitt identified-organization (4) etsi (0) mobileDomainId (0)
   gsmNetworkId(1) moduleId (3) map-OperationAndMaintenanceOperations (6)
   version2 (2)}

--<B--	SendInfoForIncomingCall,--B>--
--<B--	ConnectToFollowingAddress,--B>--
--<B--	ProcessCallWaiting,--B>--
--<B--	SendInfoForOutgoingCall,--B>--
	SendRoutingInfo,
	ProvideRoamingNumber--<B--,--B>--
--<B--	CompleteCall--B>--
FROM MAP-CallHandlingOperations {
   ccitt identified-organization (4) etsi (0) mobileDomainId (0)
   gsmNetworkId(1) moduleId (3) map-CallHandlingOperaations (7)
   version2 (2)}

	RegisterSS,
	EraseSS,
	ActivateSS,
	DeactivateSS,
	InterrogateSS,
--<B--	InvokeSS,--B>--
	ProcessUnstructuredSS-Data,
	ProcessSS-Request,
	SS-GetDigits,
	SS-GetString,
	UnstructuredNotifySS,
	RegisterPassword,
	GetPassword,
	BeginSubscriberActivity
FROM MAP-SupplementaryServiceOperations {
   ccitt identified-organization (4) etsi (0) mobileDomainId (0)
   gsmNetworkId(1) moduleId (3) map-SupplementaryServiceOperations (8)
   version2 (2)}

	SendRoutingInfoForSM,
	ForwardSM,
	ReportSM-DeliveryStatus,
	NoteSubscriberPresent,
	AlertServiceCentre,
	InformServiceCentre,
--<B--	SendInfoForMT-SMS,--B>--
--<B--	SendInfoForMO-SMS,--B>--
	ReadyForSM
FROM MAP-ShortMessageServiceOperations {
   ccitt identified-organization (4) etsi (0) mobileDomainId (0)
   gsmNetworkId(1) moduleId (3) map-ShortMessageServieOperations (9)
   version2 (2)}

	SystemFailure,
	DataMissing,
	UnexpectedDataValue,
	FacilityNotSupported,
	UnknownSubscriber,
	NumberChanged,
	UnknownBaseStation,
	UnknownMSC,
--<B--	UnknownLocArea,--B>--
	UnidentifiedSubscriber,
--<B--	UnallocatedRoamingNumber,--B>--
	UnknownEquipment,
	RoamingNotAllowed,
	IllegalSubscriber,
	IllegalEquipment,
	BearerServiceNotProvisioned,
	TeleserviceNotProvisioned,
	InvalidTargetBaseStation,
	NoRadioResourceAvailable,
	NoHandoverNumberAvailable,
	SubsequentHandoverFailure,
	TracingBufferFull,
	NoRoamingNumberAvailable,
	AbsentSubscriber,
--<B--	BusySubscriber,--B>--
--<B--	NoSubscriberReply,--B>--
--<B--	RadioCongestion,--B>--
--<B--	ImpossibleCallCompletion,--B>--
	CallBarred,
	ForwardingViolation,
	CUG-Reject,
	IllegalSS-Operation,
	SS-ErrorStatus,
	SS-NotAvailable,
	SS-SubscriptionViolation,
	SS-Incompatibility,
	SS-NotDelivered,
	PW-RegistrationFailure,
	NegativePW-Check,
	NumberOfPW-AttemptsViolation,
	SM-DeliveryFailure,
	MessageWaitingListFull
FROM MAP-Errors {
   ccitt identified-organization (4) etsi (0) mobileDomainId (0)
   gsmNetworkId(1) moduleId (3) map-Errors (10) version2 (2)}
;


-- location registration operation codes

updateLocation  UpdateLocation ::= localValue 2
cancelLocation  CancelLocation ::= localValue 3
purgeMS  PurgeMS ::= localValue 67
-- NU1 purgeMS must not be used in version 1
sendIdentification  SendIdentification::= localValue 55
-- NU1 sendIdentification must not be used in version 1


-- handover operation codes

performHandover  PerformHandover ::= localValue 28
sendEndSignal  SendEndSignal ::= localValue 29
processAccessSignalling  ProcessAccessSignalling ::= localValue 33
forwardAccessSignalling  ForwardAccessSignalling ::= localValue 34
performSubsequentHandover  PerformSubsequentHandover ::= localValue 30


-- authentication operation codes

sendAuthenticationInfo  SendAuthenticationInfo ::= localValue 56
-- NU1 sendAuthenticationInfo must not be used in version 1


-- IMEI management operation codes

checkIMEI  CheckIMEI ::= localValue 43


-- subscriber management operation codes

sendParameters  SendParameters ::= localValue 9
-- NU>1 sendParameters must not be used in version greater 1
insertSubscriberData  InsertSubscriberData ::= localValue 7
deleteSubscriberData  DeleteSubscriberData ::= localValue 8


-- fault recovery operation codes

reset  Reset ::= localValue 37
forwardCheckSS-Indication  ForwardCheckSS-Indication ::= localValue 38
restoreData  RestoreData ::= localValue 57
-- NU1 restoreData must not be used in version 1


-- operation and maintenance operation codes

activateTraceMode  ActivateTraceMode ::= localValue 50
deactivateTraceMode  DeactivateTraceMode ::= localValue 51
traceSubscriberActivity  TraceSubscriberActivity ::= localValue 52
noteInternalHandover  NoteInternalHandover ::= localValue 35
sendIMSI  SendIMSI ::= localValue 58
-- NU1 sendIMSI must not be used in version 1


-- call handling operation codes

sendRoutingInfo  SendRoutingInfo ::= localValue 22
provideRoamingNumber  ProvideRoamingNumber ::= localValue 4


-- supplementary service handling operation codes

registerSS  RegisterSS ::= localValue 10
eraseSS  EraseSS ::= localValue 11
activateSS  ActivateSS ::= localValue 12
deactivateSS  DeactivateSS ::= localValue 13
interrogateSS  InterrogateSS ::= localValue 14
processUnstructuredSS-Data  ProcessUnstructuredSS-Data ::= localValue 19
-- NU>1 processUnstructuredSS-Data must not be used in version greater 1
processSS-Request  ProcessSS-Request ::= localValue 59
-- NU1 processSS-Request must not be used in version 1
ss-GetDigits  SS-GetDigits ::= localValue 60
-- NU1 ss-GetDigits must not be used in version 1
ss-GetString  SS-GetString ::= localValue 61
-- NU1 ss-GetString must not be used in version 1
unstructuredNotifySS  UnstructuredNotifySS ::= localValue 62
-- NU1 unstructuredNotifySS must not be used in version 1
registerPassword  RegisterPassword ::= localValue 17
getPassword  GetPassword ::= localValue 18
beginSubscriberActivity  BeginSubscriberActivity ::= localValue 54
-- NU>1 beginSubscriberActivity must not be used in version greater 1


-- short message service operation codes

sendRoutingInfoForSM  SendRoutingInfoForSM ::= localValue 45
forwardSM  ForwardSM ::= localValue 46
reportSM-DeliveryStatus  ReportSM-DeliveryStatus ::= localValue 47
noteSubscriberPresent  NoteSubscriberPresent ::= localValue 48
-- NU>1 noteSubscriberPresent must not be used in version greater 1
alertServiceCentre  AlertServiceCentre ::= localValue 49
informServiceCentre  InformServiceCentre ::= localValue 63
-- NU1 informServiceCentre must not be used in version 1
readyForSM  ReadyForSM ::= localValue 66
-- NU1 readyForSM must not be used in version 1


-- generic error codes

systemFailure  SystemFailure ::= localValue 34
dataMissing  DataMissing ::= localValue 35
unexpectedDataValue  UnexpectedDataValue ::= localValue 36
facilityNotSupported  FacilityNotSupported ::= localValue 21


-- identification and numbering error codes

unknownSubscriber  UnknownSubscriber ::= localValue 1
numberChanged  NumberChanged ::= localValue 44
unknownBaseStation  UnknownBaseStation ::= localValue 2
unknownMSC  UnknownMSC ::= localValue 3
unidentifiedSubscriber  UnidentifiedSubscriber ::= localValue 5
unknownEquipment  UnknownEquipment ::= localValue 7


-- subscription error codes

roamingNotAllowed  RoamingNotAllowed ::= localValue 8
illegalSubscriber  IllegalSubscriber ::= localValue 9
illegalEquipment  IllegalEquipment ::= localValue 12
bearerServiceNotProvisioned  BearerServiceNotProvisioned ::= localValue 10
teleserviceNotProvisioned  TeleserviceNotProvisioned ::= localValue 11


-- handover error codes

invalidTargetBaseStation  InvalidTargetBaseStation ::= localValue 23
noRadioResourceAvailable  NoRadioResourceAvailable ::= localValue 24
noHandoverNumberAvailable  NoHandoverNumberAvailable ::= localValue 25
subsequentHandoverFailure  SubsequentHandoverFailure ::= localValue 26


-- operation and maintenance error codes

tracingBufferFull  TracingBufferFull ::= localValue 40


-- call handling error codes

noRoamingNumberAvailable  NoRoamingNumberAvailable ::= localValue 39
absentSubscriber  AbsentSubscriber ::= localValue 27
callBarred  CallBarred ::= localValue 13
forwardingViolation  ForwardingViolation ::= localValue 14
cug-Reject  CUG-Reject ::= localValue 15


-- supplementary service error codes

illegalSS-Operation  IllegalSS-Operation ::= localValue 16
ss-ErrorStatus  SS-ErrorStatus ::= localValue 17
ss-NotAvailable  SS-NotAvailable ::= localValue 18
ss-SubscriptionViolation  SS-SubscriptionViolation ::= localValue 19
ss-Incompatibility  SS-Incompatibility ::= localValue 20
ss-NotDelivered  SS-NotDelivered ::= localValue 42
-- NU1 ss-NotDelivered must not be used in version 1
pw-RegistrationFailure  PW-RegistrationFailure ::= localValue 37
negativePW-Check  NegativePW-Check ::= localValue 38
numberOfPW-AttemptsViolation  NumberOfPW-AttemptsViolation ::= localValue 43
-- NU1 numberOfPW-AttemptsViolation must not be used in version 1


-- short message service error codes

sm-DeliveryFailure  SM-DeliveryFailure ::= localValue 32
messageWaitingListFull  MessageWaitingListFull ::= localValue 33


END
-- MODULE END
