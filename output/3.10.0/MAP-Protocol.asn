-- ASN.1 definition for GSM MAP (Version 1)
--
-- Taken from GSM/3GPP TS 09.02 Version 3.10.0 (October 1994) from
-- http://www.3gpp.org/ftp/Specs/archive/09_series/09.02/0902-3a0.zip
-- (C) Copyright 1991-1994 by ETSI
--
-- Extracted using asn1_docextract as it is available from
--	http://cgit.osmocom.org/cgit/asn1_docextract/
--
-- Manual fixups and conversion from OPERATION MACRO to OPERATION CLASS
-- (C) 2011 by Harald Welte <laforge@gnumonks.org>
--
-- For more history, see the following blog posts
--	http://laforge.gnumonks.org/weblog/2011/03/26
--	http://laforge.gnumonks.org/weblog/2011/03/27
--	http://laforge.gnumonks.org/weblog/2011/04/09
--
MAP-Protocol DEFINITIONS ::=

BEGIN
IMPORTS
	OPERATION
FROM 
	Remote-Operations-Information-Objects
	{ joint-iso-itu-t remote-operations(4) informationObjects(5) version1(0)}

	-- Location management
	updateLocationArea, updateLocation, cancelLocation, detachIMSI,
	attachIMSI, deregisterMobileSubscriber,

	-- Data management
	sendParameters, insertSubscriberData, deleteSubscriberData,

	-- Supplementary Services Handling
	registerSS, eraseSS, activateSS, deactivateSS, interrogateSS, invokeSS,
	forwardSsNotification, registerPassword, getPassword,
	processUnstructuredSsData,

	-- Call set-up
	sendInfoForIncomingCall, sendInfoForOutgoingCall,
	sendRoutingInformation, provideRoamingNumber,

	-- Paging
	page, searchForMobileSubscriber,

	-- Handover
	performHandover, sendEndSignal,
	performSubsequentHandover, allocateHandoverNumber, sendHandoverReport,

	-- Charging
	registerChargingInformation,

	-- Restoration
	reset, forwardCheckSsIndication,

	-- Authentication and security
	forwardNewTMSI, setCipheringMode,

	-- Equipment management
	checkIMEI,

	-- Short messages
	noteMSPresent, alertServiceCentre,

	-- Tracing
	activateTraceMode, deactivateTraceMode, traceSubscriberActivity,

	-- Others
	processAccessRequest
FROM
	MAP-Operations

	-- imports error types
	unknownSubscriber, unknownBaseStation, unknownMSC, unknownLocArea,
	unidentifiedSubscriber, unallocatedRoamingNumber, unknownEquipment,
	roamingNotAllowed, teleServiceNotProvisioned,
	insufficientBearerCapabilities, callBarred, forwardingViolation,
	cug-Reject, illegalSS-Operation, ss-ErrorStatus, ss-NotAvailable,
	ss-SubscriptionViolation, ss-Incompatibility, facilityNotSupported,
	invalidTargetBaseStation, noRadioResourceAvailable,
	noHandoverNumberAvailable, subsequentHandoverFailure, absentSubscriber,
	busySubscriber, noSubscriberReply, radioCongestion,
	unexpectedDataValue, passwordRegistrationFailure,
	negativePasswordCheck, noRoamingNumberAvailable, tracingBufferFull
FROM
	MAP-Errors;

Supported-MAP-Operations OPERATION ::= {
	updateLocationArea | updateLocation | cancelLocation |
	detachIMSI | attachIMSI | deregisterMobileSubscriber |
	-- Data management
	sendParameters | insertSubscriberData | deleteSubscriberData |
	-- Supplementary Services Handling
	registerSS | eraseSS | activateSS |
	deactivateSS | interrogateSS | invokeSS | forwardSsNotification |
	registerPassword | getPassword | processUnstructuredSsData |
	-- Call set-up
	sendInfoForIncomingCall | sendInfoForOutgoingCall | sendRoutingInformation | provideRoamingNumber |
	-- Paging
	page | searchForMobileSubscriber |
	-- Handover
	performHandover | sendEndSignal |
	performSubsequentHandover | allocateHandoverNumber | sendHandoverReport |
	-- Charging
	registerChargingInformation |
	-- Restoration
	reset | forwardCheckSsIndication |
	-- Authentication and security
	forwardNewTMSI | setCipheringMode |
	-- Equipment management
	checkIMEI |
	-- Short messages
	noteMSPresent | alertServiceCentre |
	-- Tracing
	activateTraceMode | deactivateTraceMode | traceSubscriberActivity |
	-- Others
	processAccessRequest
}

END
