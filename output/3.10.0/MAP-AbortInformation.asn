-- ASN.1 definition for GSM MAP (Version 1)
--
-- Taken from GSM/3GPP TS 09.02 Version 3.10.0 (October 1994) from
-- http://www.3gpp.org/ftp/Specs/archive/09_series/09.02/0902-3a0.zip
-- (C) Copyright 1991-1994 by ETSI
--
-- Extracted using asn1_docextract as it is available from
--	http://cgit.osmocom.org/cgit/asn1_docextract/
--
-- Manual fixups and conversion from OPERATION MACRO to OPERATION CLASS
-- (C) 2011 by Harald Welte <laforge@gnumonks.org>
--
-- For more history, see the following blog posts
--	http://laforge.gnumonks.org/weblog/2011/03/26
--	http://laforge.gnumonks.org/weblog/2011/03/27
--	http://laforge.gnumonks.org/weblog/2011/04/09
--
MAP-AbortInformation  DEFINITIONS ::=

BEGIN

IMPORTS
	maxSignalInfoLength
FROM 
	MAP-Constants;

MAPAbortInformation	 ::= SEQUENCE{
		abortCause ENUMERATED{
			unspecifiedReason (0),
			versionNotSupported (1),
			userResourceLimitation (2),
			resourceUnavailableLongTermProblem (3),
			resourceUnavailableTemporaryProblem (4),
			networkPathRelease (6),
			callRelease (7),
			associatedProcedureFailed (8),
			remoteOperationFailure (9)},
		additionalInformation OCTET STRING (SIZE(1..maxSignalInfoLength))}
		--
		-- is up to the operator
		
END
