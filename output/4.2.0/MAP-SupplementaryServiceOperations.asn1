-- MODULE 'MAP-SupplementaryServiceOperations' START
MAP-SupplementaryServiceOperations {
   ccitt identified-organization (4) etsi (0) mobileDomainId (0) gsmNetworkId(1)
   moduleId (3) map-SupplementaryServiceOperations (8) version2 (2)}

DEFINITIONS

::=

BEGIN

EXPORTS
	RegisterSS,
	EraseSS,
	ActivateSS,
	DeactivateSS,
	InterrogateSS,
	InvokeSS,
	ProcessUnstructuredSS-Data,
	ProcessSS-Request,
	SS-GetDigits,
	SS-GetString,
	UnstructuredNotifySS,
	RegisterPassword,
	GetPassword,
	BeginSubscriberActivity
;

IMPORTS
	OPERATION
FROM TCAPMessages {ccitt recommendation q 773 modules(2) messages (1)}

	SystemFailure,
	DataMissing,
	UnexpectedDataValue,
	UnknownSubscriber,
	UnidentifiedSubscriber,
	BearerServiceNotProvisioned,
	TeleserviceNotProvisioned,
	AbsentSubscriber,
	CallBarred,
	IllegalSS-Operation,
	SS-ErrorStatus,
	SS-NotAvailable,
	SS-SubscriptionViolation,
	SS-Incompatibility,
	SS-PartialAcceptance,
	SS-NotDelivered,
	PW-RegistrationFailure,
	NegativePW-Check,
	NumberOfPW-AttemptsViolation
FROM MAP-Errors {
   ccitt identified-organization (4) etsi (0) mobileDomainId (0) gsmNetworkId(1)
   moduleId (3) map-Errors (10) version2 (2)}

	RegisterSS-Arg,
	SS-Info,
	SS-ForBS-Code,
	InterrogateSS-Res,
	SS-UserData,
	ProcessSS-RequestArg,
	SS-DigitString,
	ToneOrDisplay,
	SS-GetDigitsArg,
	SS-GetStringArg,
	SS-GetStringRes,
	Password,
	GuidanceInfo,
	BeginSubscriberActivityArg
FROM MAP-SS-DataTypes {
   ccitt identified-organization (4) etsi (0) mobileDomainId (0) gsmNetworkId(1)
   moduleId (3) map-SS-DataTypes (14) version2 (2)}

	SS-Code
FROM MAP-SS-Code {
   ccitt identified-organization (4) etsi (0) mobileDomainId (0) gsmNetworkId(1)
   moduleId (3) map-SS-Code (15) version2 (2)}
;


-- supplementary service handling operations

RegisterSS ::= OPERATION				--Timer m--
	ARGUMENT
		registerSS-Arg	RegisterSS-Arg
	RESULT
		ss-Info	SS-Info
		-- optional
	ERRORS {
		SystemFailure,
		DataMissing,
		UnexpectedDataValue,
		UnknownSubscriber,
		-- NU>1 UnknownSubscriber must not be used in version greater 1
		BearerServiceNotProvisioned,
		TeleserviceNotProvisioned,
		CallBarred,
		-- NU1 CallBarred must not be used in version 1
		IllegalSS-Operation,
		SS-ErrorStatus,
		SS-NotAvailable,
		SS-SubscriptionViolation,
		SS-Incompatibility,
		SS-PartialAcceptance}
		-- NU1 SS-PartialAcceptance must not be used in version 1

EraseSS ::= OPERATION					--Timer m--
	ARGUMENT
		ss-ForBS	SS-ForBS-Code
	RESULT
		ss-Info	SS-Info
		-- optional
	ERRORS {
		SystemFailure,
		DataMissing,
		-- NU1 DataMissing must not be used in version 1
		UnexpectedDataValue,
		UnknownSubscriber,
		-- NU>1 UnknownSubscriber must not be used in version greater 1
		CallBarred,
		-- NU1 CallBarred must not be used in version 1
		IllegalSS-Operation,
		SS-ErrorStatus,
		SS-SubscriptionViolation}

ActivateSS ::= OPERATION				--Timer m--
	ARGUMENT
		ss-ForBS	SS-ForBS-Code
	RESULT
		ss-Info	SS-Info
		-- optional
	ERRORS {
		SystemFailure,
		DataMissing,
		-- NU1 DataMissing must not be used in version 1
		UnexpectedDataValue,
		UnknownSubscriber,
		-- NU>1 UnknownSubscriber must not be used in version greater 1
		BearerServiceNotProvisioned,
		-- NU1 BearerServiceNotProvisioned must not be used in version 1
		TeleserviceNotProvisioned,
		-- NU1 TeleserviceNotProvisioned must not be used in version 1
		CallBarred,
		-- NU1 CallBarred must not be used in version 1
		IllegalSS-Operation,
		SS-ErrorStatus,
		SS-NotAvailable,
		SS-SubscriptionViolation,
		SS-Incompatibility,
		SS-PartialAcceptance,
		-- NU1 SS-PartialAcceptance must not be used in version 1
		NegativePW-Check,
		NumberOfPW-AttemptsViolation}

DeactivateSS ::= OPERATION				--Timer m--
	ARGUMENT
		ss-ForBS	SS-ForBS-Code
	RESULT
		ss-Info	SS-Info
		-- optional
	ERRORS {
		SystemFailure,
		DataMissing,
		-- NU1 DataMissing must not be used in version 1
		UnexpectedDataValue,
		UnknownSubscriber,
		-- NU>1 UnknownSubscriber must not be used in version greater 1
		CallBarred,
		-- NU1 CallBarred must not be used in version 1
		IllegalSS-Operation,
		SS-ErrorStatus,
		SS-SubscriptionViolation,
		NegativePW-Check,
		NumberOfPW-AttemptsViolation}
		-- NU1 NumberOfPW-AttemptsViolation must not be used in version 1

InterrogateSS ::= OPERATION				--Timer m--
	ARGUMENT
		ss-ForBS	SS-ForBS-Code
	RESULT
		interrogateSS-Res	InterrogateSS-Res
	ERRORS {
		SystemFailure,
		DataMissing,
		-- NU1 DataMissing must not be used in version 1
		UnexpectedDataValue,
		UnknownSubscriber,
		-- NU>1 UnknownSubscriber must not be used in version greater 1
		BearerServiceNotProvisioned,
		-- NU1 BearerServiceNotProvisioned must not be used in version 1
		TeleserviceNotProvisioned,
		-- NU1 TeleserviceNotProvisioned must not be used in version 1
		CallBarred,
		IllegalSS-Operation,
		SS-NotAvailable}
		-- NU>1 SS-NotAvailable must not be used in version greater 1

InvokeSS ::= OPERATION					--Timer m--
	ARGUMENT
		ss-ForBS	SS-ForBS-Code
	RESULT zzzz-Empty	NULL
	ERRORS {
		SystemFailure,
		DataMissing,
		UnexpectedDataValue,
		CallBarred,
		-- NU1 CallBarred must not be used in version 1--
		IllegalSS-Operation,
		SS-ErrorStatus,
		SS-NotAvailable}

ProcessUnstructuredSS-Data ::= OPERATION		--Timer m--
	ARGUMENT
		ss-UserData	SS-UserData
	RESULT
		ss-UserData	SS-UserData
		-- optional
	ERRORS {
		SystemFailure,
		DataMissing,
		-- NU1 DataMissing must not be used in version 1
		UnexpectedDataValue}

ProcessSS-Request ::= OPERATION				--Timer ml--
	ARGUMENT
		processSS-RequestArg	ProcessSS-RequestArg
	RESULT
		toneOrDisplay	ToneOrDisplay
	ERRORS {
		SystemFailure,
		DataMissing,
		UnexpectedDataValue,
		UnknownSubscriber,
		CallBarred}

SS-GetDigits ::= OPERATION				--Timer ml--
	ARGUMENT
		ss-GetDigitsArg	SS-GetDigitsArg
	RESULT
		ss-DigitString	SS-DigitString

SS-GetString ::= OPERATION				--Timer ml--
	ARGUMENT
		ss-GetStringArg	SS-GetStringArg
	RESULT
		ss-GetStringRes	SS-GetStringRes

UnstructuredNotifySS ::= OPERATION				--Timer ml--
	ARGUMENT
		toneOrDisplay	ToneOrDisplay
	ERRORS {
		SystemFailure,
		DataMissing,
		UnexpectedDataValue,
		UnidentifiedSubscriber,
		AbsentSubscriber,
		SS-NotDelivered}

RegisterPassword ::= OPERATION				--Timer m--
	ARGUMENT
		ss-Code	SS-Code
	RESULT
		newPassword	Password
	ERRORS {
		SystemFailure,
		DataMissing,
		-- NU1 DataMissing must not be used in version 1
		UnexpectedDataValue,
		CallBarred,
		-- NU1 CallBarred must not be used in version 1
		SS-SubscriptionViolation,
		PW-RegistrationFailure,
		NegativePW-Check,
		NumberOfPW-AttemptsViolation}
		-- NU1 NumberOfPW-AttemptsViolation must not be used in version 1
	LINKED {
		GetPassword}

GetPassword ::= OPERATION				--Timer m--
	ARGUMENT
		guidanceInfo	GuidanceInfo
	RESULT
		currentPassword	Password

BeginSubscriberActivity ::= OPERATION			--Timer m--
	ARGUMENT
		beginSubscriberActivityArg	BeginSubscriberActivityArg


END
-- MODULE END
