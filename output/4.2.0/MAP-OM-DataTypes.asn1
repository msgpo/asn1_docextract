-- MODULE 'MAP-OM-DataTypes' START
MAP-OM-DataTypes {
   ccitt identified-organization (4) etsi (0) mobileDomainId (0) gsmNetworkId(1)
   moduleId (3) map-OM-DataTypes (12) version2 (2)}

DEFINITIONS

IMPLICIT TAGS

::=

BEGIN

EXPORTS
	ActivateTraceModeArg,
	DeactivateTraceModeArg,
	TraceSubscriberActivityArg,
	NoteInternalHO-Arg
;

IMPORTS
	AddressString,
	ExternalSignalInfo,
	IMSI,
	GlobalCellId
FROM MAP-CommonDataTypes {
   ccitt identified-organization (4) etsi (0) mobileDomainId (0) gsmNetworkId(1)
   moduleId (3) map-CommonDataTypes (18) version2 (2)}
;


ActivateTraceModeArg ::= SEQUENCE {
	imsi			[0] IMSI		OPTIONAL,
	traceReference	[1] TraceReference,
	traceType	[2] TraceType,
	omc-Id		[3] AddressString	OPTIONAL}

TraceReference ::= OCTET STRING (SIZE (1..2))

TraceType ::= INTEGER {
	allEvents  (0),
	onlyCalls  (1),
	eventSet1  (2),
	eventSet254  (255)}
	(0..255)
	-- Identifiers eventSet1 to eventSet254  correspond to sets of events
	-- predefined by each operator.

DeactivateTraceModeArg ::= SEQUENCE {
	imsi			[0] IMSI		OPTIONAL,
	traceReference	[1] TraceReference}

TraceSubscriberActivityArg ::= SEQUENCE {
	imsi			[0] IMSI		OPTIONAL,
	traceReference	[1] TraceReference,
	traceType	[2] TraceType,
	omc-Id		[3] AddressString	OPTIONAL,
	callReference	[4] CallReference	OPTIONAL}

CallReference ::= OCTET STRING (SIZE (1..3))

NoteInternalHO-Arg ::= SEQUENCE {
	handoverType	HandoverType,
	targetCellId	[1] GlobalCellId	OPTIONAL,
	channelId	[2] ExternalSignalInfo	OPTIONAL}

HandoverType ::= ENUMERATED {
	interBSS  (0),
	intraBSS  (1)}


END
-- MODULE END
