-- MODULE 'MAP-CH-DataTypes' START
MAP-CH-DataTypes {
   ccitt identified-organization (4) etsi (0) mobileDomainId (0) gsmNetworkId(1)
   moduleId (3) map-CH-DataTypes (13) version2 (2)}

DEFINITIONS

IMPLICIT TAGS

::=

BEGIN

EXPORTS
	InfoForIC-Arg,
	ConnectToFollowingAddressArg,
	ProcessCallWaitingArg,
	InfoForOC-Arg,
	SendRoutingInfoArg,
	SendRoutingInfoRes,
	ProvideRoamingNumberArg,
	CompleteCallArg
;

IMPORTS
	NoReplyConditionTime,
	CUG-Index,
	CUG-Interlock,
	SS-DataList,
	ForwardingData
FROM MAP-SS-DataTypes {
   ccitt identified-organization (4) etsi (0) mobileDomainId (0) gsmNetworkId(1)
   moduleId (3) map-SS-DataTypes (14) version2 (2)}

	ISDN-AddressString,
	ExternalSignalInfo,
	IMSI,
	IMEI,
	LMSI,
	Category,
	BasicServiceCode
FROM MAP-CommonDataTypes {
   ccitt identified-organization (4) etsi (0) mobileDomainId (0) gsmNetworkId(1)
   moduleId (3) map-CommonDataTypes (18) version2 (2)}
;


InfoForIC-Arg ::= SEQUENCE {
	roamingNumber	[0] ISDN-AddressString,
	basicService	BasicServiceCode	OPTIONAL,
		dialledNumber	[5] ISDN-AddressString	OPTIONAL,
	cug-CheckInfo	[6] CUG-CheckInfo	OPTIONAL,
	-- OA1 cug-CHeckInfo must be absent in version 1
	numberOfForwarding	[7] NumberOfForwarding	OPTIONAL}

CUG-CheckInfo ::= SEQUENCE {
	cug-Interlock	CUG-Interlock,
	cug-OutgoingAccess	NULL			OPTIONAL}

NumberOfForwarding ::= INTEGER (1..5)

ConnectToFollowingAddressArg ::= SEQUENCE {
	forwardingData	ForwardingData,
	msisdn		ISDN-AddressString	OPTIONAL,
	cug-CheckInfo	CUG-CheckInfo	OPTIONAL}
	-- OA1 cug-CheckInfo must be absent in version 1

ProcessCallWaitingArg ::= SEQUENCE {
	msisdn		[0] ISDN-AddressString,
	cug-Index	[1] CUG-Index	OPTIONAL,
	gsm-BearerCapability	[2] ExternalSignalInfo	OPTIONAL,
	networkSignalInfo	[3] ExternalSignalInfo	OPTIONAL,
	noReplyConditionTime	[4] NoReplyConditionTime	OPTIONAL,
	ss-DataList	[5] SS-DataList	OPTIONAL}

InfoForOC-Arg ::= SEQUENCE {
	calledNumber	[0] ISDN-AddressString,
	basicService	BasicServiceCode	OPTIONAL,
	cug-Index	[4] CUG-Index	OPTIONAL,
	-- OA1 cug-Index must be absent in version 1
	supressPrefCUG	[5] NULL		OPTIONAL,
	-- OA1 supressPrefCUG must be absent in version 1
	supressOutgoingAccess	[6] NULL		OPTIONAL}
	-- OA1 supressOutgoingAccess must be absent in version 1

SendRoutingInfoArg ::= SEQUENCE {
	msisdn		[0] ISDN-AddressString,
	cug-CheckInfo	[1] CUG-CheckInfo	OPTIONAL,
	-- OA1 cug-CheckInfo must be absent in version 1
	numberOfForwarding	[2] NumberOfForwarding	OPTIONAL,
	networkSignalInfo	[10] ExternalSignalInfo	OPTIONAL}

SendRoutingInfoRes ::= SEQUENCE {
	imsi			IMSI,
	routingInfo	RoutingInfo,
	cug-CheckInfo	CUG-CheckInfo	OPTIONAL}
	-- OA1 cug-CheckInfo must be absent in version 1

RoutingInfo ::= CHOICE {
	roamingNumber	ISDN-AddressString,
	forwardingData	ForwardingData}

ProvideRoamingNumberArg ::= SEQUENCE {
	imsi			[0] IMSI,
	msc-Number	[1] ISDN-AddressString	OPTIONAL,
	-- OP>1 msc-Number must be present in version greater 1
	msisdn		[2] ISDN-AddressString	OPTIONAL,
	previousRoamingNumber	[3] ISDN-AddressString	OPTIONAL,
	lmsi			[4] LMSI		OPTIONAL,
	gsm-BearerCapability	[5] ExternalSignalInfo	OPTIONAL,
	networkSignalInfo	[6] ExternalSignalInfo	OPTIONAL}

CompleteCallArg ::= SEQUENCE {
	msisdnOrIMEI	MSISDN-OrIMEI,
	category		[1] Category	OPTIONAL,
	cug-Index	[2] CUG-Index	OPTIONAL,
	-- NU1 cug-INDEX must not be used in version 1
	gsm-BearerCapability	[3] ExternalSignalInfo	OPTIONAL,
	networkSignalInfo	[7] ExternalSignalInfo	OPTIONAL,
	-- OA1 networkSignalInfo must be absent in version 1
	noReplyConditionTime	[4] NoReplyConditionTime	OPTIONAL,
	ss-DataList	[5] SS-DataList	OPTIONAL,
	cug-CheckInfo	[6] CUG-CheckInfo	OPTIONAL}
	-- OA1 cug-CheckInfo must be absent in version 1

MSISDN-OrIMEI ::= CHOICE {
	msisdn		[0] ISDN-AddressString,
	imei			[8] IMEI}
	-- NU1 imei must not be used in version 1


END
-- MODULE END
