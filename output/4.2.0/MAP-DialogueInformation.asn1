-- MODULE 'MAP-DialogueInformation' START
MAP-DialogueInformation {
   ccitt identified-organization (4) etsi (0) mobileDomainId (0) gsmNetworkId(1)
   moduleId (3) map-DialogueInformation (3) version2 (2)}

DEFINITIONS

IMPLICIT TAGS

::=

BEGIN

IMPORTS
	gsm-Network,
	as-Id
FROM MobileDomainDefinitions {
   ccitt (0) identified-organization (4) etsi (0) mobileDomainId (0)
   mobileDomainDefinitions (0) version1 (1)}

	AddressString
FROM MAP-CommonDataTypes {
   ccitt identified-organization (4) etsi (0) mobileDomainId (0) gsmNetworkId(1)
   moduleId (3) map-CommonDataTypes (18) version2 (2)}
;


-- abstract syntax name for MAP-DialoguePDU

map-DialogueAS  OBJECT IDENTIFIER ::=
	{gsm-Network as-Id map-DialoguePDU (1) version1 (1)}

MAP-DialoguePDU ::= CHOICE {
	map-open	[0] MAP-OpenInfo,
	map-accept	[1] MAP-AcceptInfo,
	map-close	[2] MAP-CloseInfo,
	map-refuse	[3] MAP-RefuseInfo,
	map-userAbort	[4] MAP-UserAbortInfo,
	map-providerAbort	[5] MAP-ProviderAbortInfo}

MAP-OpenInfo ::= SEQUENCE {
	destinationReference	[0] AddressString	OPTIONAL,
	originationReference	[1] AddressString	OPTIONAL,
	plmn-specificInfo	[2] EXTERNAL	OPTIONAL}

MAP-AcceptInfo ::= SEQUENCE {
	plmn-specificInfo	[0] EXTERNAL	OPTIONAL}

MAP-CloseInfo ::= SEQUENCE {
	plmn-specificInfo	[0] EXTERNAL	OPTIONAL}

MAP-RefuseInfo ::= SEQUENCE {
	reason	Reason,
	plmn-specificInfo	[0] EXTERNAL	OPTIONAL}

Reason ::= ENUMERATED {
	noReasonGiven  (0),
	invalidDestinationReference  (1)}

MAP-UserAbortInfo ::= SEQUENCE {
	map-UserAbortChoice	MAP-UserAbortChoice,
	plmn-specific	[0] EXTERNAL	OPTIONAL}

MAP-UserAbortChoice ::= CHOICE {
	userSpecificReason	[0] NULL,
	userResourceLimitation	[1] NULL,
	resourceUnavailable	[2] ResourceUnavailableReason,
	applicationProcedureCancellation	[3] ProcedureCancellationReason}

ResourceUnavailableReason ::= ENUMERATED {
	shortTermResourceLimitation  (0),
	longTermResourceLimitation  (1)}

ProcedureCancellationReason ::= ENUMERATED {
	handoverCancellation  (0),
	radioChannelRelease  (1),
	networkPathRelease  (2),
	callRelease  (3),
	associatedProcedureFailure  (4),
	tandemDialogueRelease (5),
	remoteOperationsFailure  (6)}

MAP-ProviderAbortInfo ::= SEQUENCE {
	map-ProviderAbortReason	MAP-ProviderAbortReason,
	plmn-specificInfo	EXTERNAL		OPTIONAL}

MAP-ProviderAbortReason ::= ENUMERATED {
	abnormalDialogue  (0),
	invalidPDU  (1)}


END
-- MODULE END
