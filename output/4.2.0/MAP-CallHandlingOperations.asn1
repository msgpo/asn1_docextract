-- MODULE 'MAP-CallHandlingOperations' START
MAP-CallHandlingOperations {
   ccitt identified-organization (4) etsi (0) mobileDomainId (0) gsmNetworkId(1)
   moduleId (3) map-CallHandlingOperations (7) version2 (2)}

DEFINITIONS

::=

BEGIN

EXPORTS
	SendInfoForIncomingCall,
	ConnectToFollowingAddress,
	ProcessCallWaiting,
	SendInfoForOutgoingCall,
	SendRoutingInfo,
	ProvideRoamingNumber,
	CompleteCall
;

IMPORTS
	OPERATION
FROM TCAPMessages {ccitt recommendation q 773 modules(2) messages (1)}

	SystemFailure,
	DataMissing,
	UnexpectedDataValue,
	FacilityNotSupported,
	UnknownSubscriber,
	NumberChanged,
	UnidentifiedSubscriber,
	UnallocatedRoamingNumber,
	BearerServiceNotProvisioned,
	TeleserviceNotProvisioned,
	NoRoamingNumberAvailable,
	AbsentSubscriber,
	BusySubscriber,
	NoSubscriberReply,
	RadioCongestion,
	ImpossibleCallCompletion,
	CallBarred,
	ForwardingViolation,
	CUG-Reject
FROM MAP-Errors {
   ccitt identified-organization (4) etsi (0) mobileDomainId (0) gsmNetworkId(1)
   moduleId (3) map-Errors (10) version2 (2)}

	InfoForIC-Arg,
	ConnectToFollowingAddressArg,
	ProcessCallWaitingArg,
	InfoForOC-Arg,
	SendRoutingInfoArg,
	SendRoutingInfoRes,
	ProvideRoamingNumberArg,
	CompleteCallArg
FROM MAP-CH-DataTypes {
   ccitt identified-organization (4) etsi (0) mobileDomainId (0) gsmNetworkId(1)
   moduleId (3) map-CH-DataTypes (13) version2 (2)}

	ISDN-AddressString
FROM MAP-CommonDataTypes {
   ccitt identified-organization (4) etsi (0) mobileDomainId (0) gsmNetworkId(1)
   moduleId (3) map-CommonDataTypes (18) version2 (2)}
;


SendInfoForIncomingCall ::= OPERATION			--Timer m--
	ARGUMENT
		infoForIC-Arg	InfoForIC-Arg
	ERRORS {
		SystemFailure,
		DataMissing,
		UnexpectedDataValue,
		UnknownSubscriber,
		UnidentifiedSubscriber,
		UnallocatedRoamingNumber,
		AbsentSubscriber,
		ForwardingViolation,
		ImpossibleCallCompletion}
	LINKED {
		CompleteCall,
		ProcessCallWaiting,
		ConnectToFollowingAddress}

ConnectToFollowingAddress ::= OPERATION			--Timer s--
	ARGUMENT
		connectToFollowingAddressArg	ConnectToFollowingAddressArg

ProcessCallWaiting ::= OPERATION				--Timer s--
	ARGUMENT
		processCallWaitingArg	ProcessCallWaitingArg
		-- optional--
		-- OA1 processCallWaitingArg must be absent in version 1--
	ERRORS {
		DataMissing,
		-- NU1 DataMissing must not be used in version 1--
		UnexpectedDataValue,
		-- NU1 UnexpectedDataValue must not be used in version 1--
		BusySubscriber,
		-- NU1 BusySubscriber must not be used in version 1--
		NoSubscriberReply}
		-- NU1 NoSubscriberReply must not be used in version 1--

SendInfoForOutgoingCall ::= OPERATION			--Timer ml--
	ARGUMENT
		infoForOC-Arg	InfoForOC-Arg
	ERRORS {
		SystemFailure,
		DataMissing,
		UnexpectedDataValue,
		UnknownSubscriber,
		BearerServiceNotProvisioned,
		TeleserviceNotProvisioned,
		CallBarred,
		CUG-Reject}
	LINKED {
		CompleteCall}

SendRoutingInfo ::= OPERATION				--Timer m--
	ARGUMENT
		sendRoutingInfoArg	SendRoutingInfoArg
	RESULT
		sendRoutingInfoRes	SendRoutingInfoRes
	ERRORS {
		SystemFailure,
		DataMissing,
		UnexpectedDataValue,
		FacilityNotSupported,
		UnknownSubscriber,
		NumberChanged,
		-- NU1 NumberChanged must not be used in version 1
	BearerServiceNotProvisioned,
		TeleserviceNotProvisioned,
		AbsentSubscriber,
		CallBarred,
		CUG-Reject,
		ForwardingViolation}

ProvideRoamingNumber ::= OPERATION				--Timer m--
	ARGUMENT
		provideRoamingNumberArg	ProvideRoamingNumberArg
	RESULT
		roamingNumber	ISDN-AddressString
	ERRORS {
		SystemFailure,
		DataMissing,
		UnexpectedDataValue,
		FacilityNotSupported,
		AbsentSubscriber,
		NoRoamingNumberAvailable}

CompleteCall ::= OPERATION				--Timer ml--
	ARGUMENT
		completeCallArg	CompleteCallArg
	ERRORS {
		DataMissing,
		UnexpectedDataValue,
		BusySubscriber,
		NoSubscriberReply,
		RadioCongestion}


END
-- MODULE END
