-- MODULE 'MAP-Frame' START
MAP-Frame

DEFINITIONS ::=

BEGIN

IMPORTS
	Component,
	MessageType
FROM TCAPMessages

	dialogue-as-id,
	DialoguePDU
FROM DialoguePDUs

	updateLocation
FROM MAP-Protocol

	map-DialogueAS,
	MAP-DialoguePDU
FROM MAP-DialogueInformation

	map-ac
FROM MAP-ApplicationContexts
;


ZZZZ-Dummy ::= NULL


END
-- MODULE END
