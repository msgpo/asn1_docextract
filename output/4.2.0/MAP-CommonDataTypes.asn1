-- MODULE 'MAP-CommonDataTypes' START
MAP-CommonDataTypes {
   ccitt identified-organization (4) etsi (0) mobileDomainId (0) gsmNetworkId(1)
   moduleId (3) map-CommonDataTypes (18) version2 (2)}

DEFINITIONS

IMPLICIT TAGS

::=

BEGIN

EXPORTS

	-- general data types and values
	TBCD-STRING,
	AddressString,
	ISDN-AddressString,
	ISDN-SubaddressString,
	ExternalSignalInfo,
	SignalInfo,
	maxSignalInfoLength,

	-- data types for numbering and identification
	IMSI,
	TMSI,
	SubscriberId,
	IMEI,
	LocAreaId,
	LocAreaIdOrNone,
	LocationInfo,
	HLR-List,
	LMSI,
	GlobalCellId,
	NetworkResource,

	-- data types for subscriber management
	Category,
	BearerServiceList,
	TeleserviceList,
	BasicServiceCode,
	BasicServiceList,
	BasicServiceGroupList,
	maxNumOfBasicServiceGroups
;

IMPORTS
	TeleserviceCode
FROM MAP-TS-Code {
   ccitt identified-organization (4) etsi (0) mobileDomainId (0) gsmNetworkId(1)
   moduleId (3) map-TS-Code (19) version2 (2)}

	BearerServiceCode
FROM MAP-BS-Code {
   ccitt identified-organization (4) etsi (0) mobileDomainId (0) gsmNetworkId(1)
   moduleId (3) map-BS-Code (20) version2 (2)}
;


-- general data types

TBCD-STRING ::= OCTET STRING
	-- This type (Telephony Binary Coded Decimal String) is used to represent
	-- several digits from 0 through 9, *, #, a, b , c, two digits per octet,
	-- each digit encoded 0000 to 1001 (0 to 9), 1010 (*), 1011 (#), 1100 (a),
	-- 1101 (b) or 1110 (c); 1111 used as filler when there is an odd number
	-- of digits.

	-- bits 8765 of octet n encoding digit 2n  
	-- bits 4321 of octet n encoding digit 2(n-1) +1 

AddressString ::= OCTET STRING (SIZE (1..maxAddressLength))
	-- This type is used to represent a number for addressing purposes. It is
	-- composed of
	--	  a)	one  octet for nature of address, and numbering plan indicator.
	--	  b)	digits of an address encoded as TBCD-String.

	-- a)	The first octet includes a one bit extension indicator, a 3 bits nature of
	-- 	address indicator and a 4 bits numbering plan indicator, encoded as
	-- 	follows:

	-- bit 8: 1  (no extension)

	-- bits 765: nature of address indicator
	--	000  unknown
	--	001  international number
	--	010  national significant number
	--	011  network specific number
	--	100  subscriber number
	--	101  reserved 
	--	110  abbreviated number
	--	111  reserved for extension

	-- bits 4321: numbering plan indicator
	--	0000  unknown
	--	0001  ISDN/Telephony Numbering Plan (Rec CCITT E.164)
	--	0010  spare
	--	0011  data numbering plan (Rec CCITT X.121)
	--	0100  telex numbering plan (Rec CCITT F.69)
	--	0101  spare
	--	0110  land mobile numbering plan (REC CCITT E.212)
	--	0111  spare
	--	1000  national numbering plan
	--	1001  private numbering plan
	--	1111  reserved for extension

	-- 	all other values are reserved.

	-- b)	The following octets representing digits of an address encoded as a
	--	TBCD-STRING.

maxAddressLength  INTEGER ::= 20

ISDN-AddressString ::= AddressString (SIZE (1..maxISDN-AddressLength))
	-- This type is used to represent ISDN numbers.

maxISDN-AddressLength  INTEGER ::= 9

ISDN-SubaddressString ::= OCTET STRING (SIZE (1..maxISDN-SubaddressLength))
	-- This type is used to represent ISDN subaddresses.

maxISDN-SubaddressLength  INTEGER ::= 21

ExternalSignalInfo ::= SEQUENCE {
	protocolId	ProtocolId,
	signalInfo	SignalInfo}
	-- This data type is defined to allow the Mobile Application Part protocol to
	-- carry information elements defined in other Recommendations/Technical
	-- Specifications without any direct reference to their internal
	-- structure.

	-- The data type represents any set of information elements (including tag
	-- and length octets) imported from another signalling protocol. For the
	-- user-network protocol, the set of elements may consist of a complete
	-- layer 3 message. The protocol to which the information elements belong is
	-- indicated by the protocolId element, while the signalling information is
	-- contained in the signalInfo element.

SignalInfo ::= OCTET STRING (SIZE (1..maxSignalInfoLength))

maxSignalInfoLength  INTEGER ::= 200
	-- This NamedValue represents the theoretical maximum number of octets
	-- which are available to carry a single data type, without requiring
	-- segmentation to cope with the network layer service. However, the actual
	-- maximum size available for a data type may be lower, especially when
	-- other information elements have to be included in the same component.

ProtocolId ::= ENUMERATED {
	gsm-0408  (1),
	gsm-0806-DTAP  (2),
	gsm-0808-BSSMAP  (3),
	isup-Q763  (4)}


-- data types for numbering and identification

IMSI ::= TBCD-STRING (SIZE (3..8))
	-- digits of MCC, MNC, MSIN are concatenated in this order.

TMSI ::= OCTET STRING (SIZE (1..4))

SubscriberId ::= CHOICE {
	imsi			[0] IMSI,
	tmsi			[1] TMSI}

IMEI ::= TBCD-STRING (SIZE (8))
	-- The internal Structure is defined as follows:
	--	type approval code: 6 digits
	--	manufacturer place: 2 digits 
	--	individual serial number: 6 digits
	--	unassigned: 1 digit

LocAreaId ::= OCTET STRING (SIZE (2..5))
	-- Octets are coded according to GSM 04.08.
	-- The internal structure is defined as follows:
	--	Mobile Country Code:	3 digits according to Rec E.212
	--			1 digit filler (1111)
	--	Mobile Network Code:	2 digits according to Rec E.212
	--	Location Area Code:	2 octets according to GSM 04.08

LocAreaIdOrNone ::= CHOICE {
	locAreaId	LocAreaId,
	noLocAreaId	NULL}

LocationInfo ::= CHOICE {
	roamingNumber	[0] ISDN-AddressString,
	-- NU>1 roamingNumber must not be used in version greater 1
	msc-Number	[1] ISDN-AddressString}

HLR-Id ::= IMSI
	-- leading digits of IMSI

HLR-List ::= SEQUENCE SIZE (1..maxNumOfHLR-Id) OF
				HLR-Id

maxNumOfHLR-Id  INTEGER ::= 50

LMSI ::= OCTET STRING (SIZE (4))

GlobalCellId ::= OCTET STRING (SIZE (5..7))
	-- Octets are coded according to GSM 04.08.
	-- The internal structure is defined as follows:
	--	Mobile Country Code:	3 digits according to Rec E.212
	--			1 digit filler (1111)
	--	Mobile Network Code:	2 digits according to Rec E.212
	--	Location Area Code:	2 octets according to GSM 04.08
	--	Cell Identity:	2 octets (CI) according to GSM 04.08

NetworkResource ::= ENUMERATED {
	plmn  (0),
	hlr  (1),
	vlr  (2),
	pvlr  (3),
	controllingMSC  (4),
	vmsc  (5),
	eir  (6),
	rss  (7)}


-- data types for subscriber management

Category ::= OCTET STRING (SIZE (1))
	-- The internal structure is defined in CCITT Rec Q.763.

BearerServiceList ::= SEQUENCE SIZE (1..maxNumOfBearerServices) OF
				BearerServiceCode

maxNumOfBearerServices  INTEGER ::= 50

TeleserviceList ::= SEQUENCE SIZE (1..maxNumOfTeleservices) OF
				TeleserviceCode

maxNumOfTeleservices  INTEGER ::= 20

BasicServiceCode ::= CHOICE {
	bearerService	[2] BearerServiceCode,
	teleservice	[3] TeleserviceCode}

BasicServiceList ::= SEQUENCE SIZE (1..maxNumOfBasicServices) OF
				BasicServiceCode

maxNumOfBasicServices  INTEGER ::= 70

BasicServiceGroupList ::= SEQUENCE SIZE (1..maxNumOfBasicServiceGroups) OF
				BasicServiceCode

maxNumOfBasicServiceGroups  INTEGER ::= 13


END
-- MODULE END
