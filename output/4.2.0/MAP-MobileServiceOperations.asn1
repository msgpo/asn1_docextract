-- MODULE 'MAP-MobileServiceOperations' START
MAP-MobileServiceOperations {
   ccitt identified-organization (4) etsi (0) mobileDomainId (0) gsmNetworkId(1)
   moduleId (3) map-MobileServiceOperations (5) version2 (2)}

DEFINITIONS

::=

BEGIN

EXPORTS

	-- location registration operations
	UpdateLocationArea,
	UpdateLocation,
	CancelLocation,
	PurgeMS,
	SendIdentification,
	DetachIMSI,
	AttachIMSI,

	-- paging management operations
	Page,
	SearchForMS,

	-- access management operations
	ProcessAccessRequest,

	-- handover operations
	PerformHandover,
	SendEndSignal,
	ProcessAccessSignalling,
	ForwardAccessSignalling,
	PerformSubsequentHandover,
	AllocateHandoverNumber,
	SendHandoverReport,

	-- authentication management operations
	Authenticate,
	SendAuthenticationInfo,

	-- security management operations
	SetCipheringMode,

	-- IMEI management operations
	CheckIMEI,
	ObtainIMEI,

	-- subscriber management operations
	SendParameters,
	InsertSubscriberData,
	DeleteSubscriberData,

	-- identity management operations
	ProvideIMSI,
	ForwardNewTMSI,

	-- fault recovery operations
	Reset,
	ForwardCheckSS-Indication,
	RestoreData
;

IMPORTS
	OPERATION
FROM TCAPMessages {ccitt recommendation q 773 modules(2) messages (1)}

	SystemFailure,
	DataMissing,
	UnexpectedDataValue,
	UnknownSubscriber,
	UnknownBaseStation,
	UnknownMSC,
	UnknownLocArea,
	UnidentifiedSubscriber,
	UnknownEquipment,
	RoamingNotAllowed,
	IllegalSubscriber,
	IllegalEquipment,
	InvalidTargetBaseStation,
	NoRadioResourceAvailable,
	NoHandoverNumberAvailable,
	SubsequentHandoverFailure,
	AbsentSubscriber,
	BusySubscriber
FROM MAP-Errors {
   ccitt identified-organization (4) etsi (0) mobileDomainId (0) gsmNetworkId(1)
   moduleId (3) map-Errors (10) version2 (2)}

	UpdateLocationAreaArg,
	UpdateLocationArg,
	UpdateLocationRes,
	CancelLocationArg,
	PurgeMS-Arg,
	SendIdentificationRes,
	PageArg,
	SearchForMS-Arg,
	ProcessAccessRequestArg,
	ProcessAccessRequestRes,
	PerformHO-Arg,
	PerformHO-Res,
	PerformSubsequentHO-Arg,
	AuthenticateArg,
	SendAuthenticationInfoArg,
	SendAuthenticationInfoRes,
	SRES,
	SetCipheringModeArg,
	CheckIMEI-Arg,
	SendParametersArg,
	SentParameterList,
	InsertSubscriberDataArg,
	InsertSubscriberDataRes,
	DeleteSubscriberDataArg,
	ResetArg,
	RestoreDataArg,
	RestoreDataRes
FROM MAP-MS-DataTypes {
   ccitt identified-organization (4) etsi (0) mobileDomainId (0) gsmNetworkId(1)
   moduleId (3) map-MS-DataTypes (11) version2 (2)}

	ISDN-AddressString,
	ExternalSignalInfo,
	IMSI,
	TMSI,
	SubscriberId,
	IMEI,
	LocAreaId
FROM MAP-CommonDataTypes {
   ccitt identified-organization (4) etsi (0) mobileDomainId (0) gsmNetworkId(1)
   moduleId (3) map-CommonDataTypes (18) version2 (2)}
;


-- location registration operations

UpdateLocationArea ::= OPERATION				--Timer m--
	ARGUMENT
		updateLocationAreaArg	UpdateLocationAreaArg
	RESULT zzzz-Empty	NULL
	ERRORS {
		SystemFailure,
		DataMissing,
		-- NU1 DataMissing must not be used in version 1--
		UnexpectedDataValue,
		UnknownSubscriber,
		UnknownLocArea,
		RoamingNotAllowed,
		IllegalSubscriber,
		IllegalEquipment}
		-- NU1 IllegalEquipment must not be used in version 1--

UpdateLocation ::= OPERATION				--Timer m--
	ARGUMENT
		updateLocationArg	UpdateLocationArg
	RESULT
		updateLocationRes	UpdateLocationRes
	ERRORS {
		SystemFailure,
		DataMissing,
		-- NU1 DataMissing must not be used in version 1
		UnexpectedDataValue,
		UnknownSubscriber,
		RoamingNotAllowed}

CancelLocation ::= OPERATION				--Timer m--
	ARGUMENT
		cancelLocationArg	CancelLocationArg
	RESULT zzzz-Empty	NULL
	ERRORS {
		DataMissing,
		-- NU1 DataMissing must not be used in version 1
		UnexpectedDataValue,
		UnidentifiedSubscriber}
		-- NU>1 UnidentifiedSubscriber must not be used in version 1

PurgeMS ::= OPERATION				--Timer m--
	ARGUMENT
		purgeMS-Arg	PurgeMS-Arg
	RESULT zzzz-Empty	NULL

SendIdentification::= OPERATION				--Timer s--
	ARGUMENT
		tmsi		TMSI
	RESULT
		sendIdentificationRes	SendIdentificationRes
	ERRORS {
		DataMissing,
		UnidentifiedSubscriber}

DetachIMSI ::= OPERATION				--Timer s--
	ARGUMENT
		subscriberId		SubscriberId

AttachIMSI ::= OPERATION				--Timer s--
	ARGUMENT
		subscriberId		SubscriberId
	RESULT zzzz-Empty	NULL
	ERRORS {
		SystemFailure,
		DataMissing,
		-- NU1 DataMissing must not be used in version 1--
		UnexpectedDataValue,
		UnknownSubscriber,
		UnidentifiedSubscriber,
		RoamingNotAllowed,
		IllegalSubscriber}


-- paging management operations

Page ::= OPERATION				--Timer m--
	ARGUMENT
		pageArg	PageArg
	ERRORS {
		SystemFailure,
		DataMissing,
		-- NU1 DataMissing must not be used in version 1--
		UnexpectedDataValue,
		UnknownLocArea,
		AbsentSubscriber,
		BusySubscriber}

SearchForMS ::= OPERATION				--Timer m--
	ARGUMENT
		searchForMS-Arg	SearchForMS-Arg
	RESULT
		currentLocAreaId	LocAreaId
	ERRORS {
		SystemFailure,
		DataMissing,
		-- NU1 DataMissing must not be used in version 1--
		UnexpectedDataValue,
		AbsentSubscriber,
		BusySubscriber}


-- access management operations

ProcessAccessRequest ::= OPERATION				--Timer m--
	ARGUMENT
		proccessAccessRequestArg	ProcessAccessRequestArg
	RESULT
		processAccessRequestRes	ProcessAccessRequestRes
	ERRORS {
		SystemFailure,
		DataMissing,
		-- NU1 DataMissing must not be used in version 1--
		UnexpectedDataValue,
		UnknownSubscriber,
		-- NU>1 UnknownSubscriber must not be used in version greater 1--
		UnknownLocArea,
		-- NU1 UnknownLocArea must not be used in version 1--
		UnidentifiedSubscriber,
		RoamingNotAllowed,
		-- NU1 RoamingNotAllowed must not be used in version 1--
		IllegalSubscriber,
		IllegalEquipment}
		-- NU1 IllegalEquipment must not be used in version 1--


-- handover operations

PerformHandover ::= OPERATION				--Timer s--
	ARGUMENT
		performHO-Arg	PerformHO-Arg
	RESULT
		performHO-Res	PerformHO-Res
	ERRORS {
		SystemFailure,
		DataMissing,
		-- NU1 DataMissing must not be used in version 1
		UnexpectedDataValue,
		UnknownBaseStation,
		InvalidTargetBaseStation,
		NoRadioResourceAvailable,
		NoHandoverNumberAvailable}

SendEndSignal ::= OPERATION				--Timer l--
	RESULT zzzz-Empty	NULL

ProcessAccessSignalling ::= OPERATION			--Timer s--
	ARGUMENT
		bss-APDU	ExternalSignalInfo

ForwardAccessSignalling ::= OPERATION			--Timer s--
	ARGUMENT
		bss-APDU	ExternalSignalInfo

PerformSubsequentHandover ::= OPERATION			--Timer m--
	ARGUMENT
		performSubsequentHO-Arg	PerformSubsequentHO-Arg
	RESULT
		accessSignalInfo	ExternalSignalInfo
	ERRORS {
		UnexpectedDataValue,
		DataMissing,
		-- NU1 DataMissing must not be used in version 1
		UnknownBaseStation,
		UnknownMSC,
		InvalidTargetBaseStation,
		SubsequentHandoverFailure}

AllocateHandoverNumber ::= OPERATION			--Timer s--
	ERRORS {
		NoHandoverNumberAvailable}
	LINKED {
		SendHandoverReport}

SendHandoverReport ::= OPERATION				--Timer l--
	ARGUMENT
		handoverNumber	ISDN-AddressString
	RESULT zzzz-Empty	NULL


-- authentication management operations

Authenticate ::= OPERATION				--Timer s--
	ARGUMENT
		authenticateArg	AuthenticateArg
	RESULT
		sres		SRES

SendAuthenticationInfo ::= OPERATION			--Timer m--
	ARGUMENT
		sendAuthenticationInfoArg	SendAuthenticationInfoArg
	RESULT
		sendAuthenticationInfoRes	SendAuthenticationInfoRes
	ERRORS {
		SystemFailure,
		DataMissing,
		UnexpectedDataValue,
		UnknownSubscriber}


-- security management operations

SetCipheringMode ::= OPERATION				--Timer s--
	ARGUMENT
		setCipheringModeArg	SetCipheringModeArg


-- IMEI management operations

CheckIMEI ::= OPERATION					--Timer m--
	ARGUMENT
		imei		IMEI
		-- optional:
		-- OP1 imei must be present in version 1
	RESULT
		checkIMEI-Arg	CheckIMEI-Arg
	ERRORS {
		SystemFailure,
		DataMissing,
		-- NU1 DataMissing must not be used in version 1
		UnexpectedDataValue,
		-- NU>1 UnexpectedDataValue must not be used in version greater 1
		UnknownEquipment}

ObtainIMEI ::= OPERATION				--Timer s--
	RESULT
		imei	IMEI
	ERRORS {
		SystemFailure}


-- subscriber management operations

SendParameters ::= OPERATION				--Timer m--
	ARGUMENT
		sendParametersArg	SendParametersArg
	RESULT
		sentParameterList	SentParameterList
		-- optional
		-- nothing is returned, if no requested parameter is available or
		-- exists
	ERRORS {
		UnexpectedDataValue,
		UnknownSubscriber,
		UnidentifiedSubscriber}

InsertSubscriberData ::= OPERATION				--Timer m--
	ARGUMENT
		insertSubscriberDataArg	InsertSubscriberDataArg
	RESULT
		insertSubscriberDataRes	InsertSubscriberDataRes
		-- optional
		-- OA1 insertSubscriberDataRes must be absent in version 1
	ERRORS {
		DataMissing,
		UnexpectedDataValue,
		UnidentifiedSubscriber}

DeleteSubscriberData ::= OPERATION				--Timer m--
	ARGUMENT
		deleteSubscriberDataArg	DeleteSubscriberDataArg
	RESULT zzzz-Empty	NULL
	ERRORS {
		DataMissing,
		UnexpectedDataValue,
		UnidentifiedSubscriber}


-- identity management operations

ProvideIMSI ::= OPERATION				--Timer s--
	RESULT
		imsi		IMSI
	ERRORS {
		DataMissing,
		-- NU1 DataMissing must not be used in version 1--
		AbsentSubscriber}

ForwardNewTMSI ::= OPERATION				--Timer s--
	ARGUMENT
		tmsi		TMSI
	RESULT zzzz-Empty	NULL


-- fault recovery operations

Reset ::= OPERATION					--Timer m--
	ARGUMENT
		resetArg	ResetArg

ForwardCheckSS-Indication ::= OPERATION			--Timer s--

RestoreData ::= OPERATION				--Timer m--
	ARGUMENT
		restoreDataArg	RestoreDataArg
	RESULT
		restoreDataRes	RestoreDataRes
	ERRORS {
		SystemFailure,
		DataMissing,
		UnexpectedDataValue,
		UnknownSubscriber}


END
-- MODULE END
