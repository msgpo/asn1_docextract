-- MODULE 'MAP-ShortMessageServiceOperations' START
MAP-ShortMessageServiceOperations {
   ccitt identified-organization (4) etsi (0) mobileDomainId (0) gsmNetworkId(1)
   moduleId (3) map-ShortMessageServiceOperations (9) version2 (2)}

DEFINITIONS

::=

BEGIN

EXPORTS
	SendRoutingInfoForSM,
	ForwardSM,
	ReportSM-DeliveryStatus,
	NoteSubscriberPresent,
	AlertServiceCentre,
	InformServiceCentre,
	SendInfoForMT-SMS,
	SendInfoForMO-SMS,
	ReadyForSM
;

IMPORTS
	OPERATION
FROM TCAPMessages {ccitt recommendation q 773 modules(2) messages (1)}

	SystemFailure,
	DataMissing,
	UnexpectedDataValue,
	FacilityNotSupported,
	UnknownSubscriber,
	UnidentifiedSubscriber,
	IllegalSubscriber,
	IllegalEquipment,
	TeleserviceNotProvisioned,
	AbsentSubscriber,
	CallBarred,
	SM-DeliveryFailure,
	MessageWaitingListFull
FROM MAP-Errors {
   ccitt identified-organization (4) etsi (0) mobileDomainId (0) gsmNetworkId(1)
   moduleId (3) map-Errors (10) version2 (2)}

	RoutingInfoForSM-Arg,
	RoutingInfoForSM-Res,
	ForwardSM-Arg,
	SM-RP-DA,
	ReportSM-DeliveryStatusArg,
	AlertServiceCentreArg,
	InformServiceCentreArg,
	ReadyForSM-Arg
FROM MAP-SM-DataTypes {
   ccitt identified-organization (4) etsi (0) mobileDomainId (0) gsmNetworkId(1)
   moduleId (3) map-SM-DataTypes (16) version2 (2)}

	AddressString,
	ISDN-AddressString,
	IMSI
FROM MAP-CommonDataTypes {
   ccitt identified-organization (4) etsi (0) mobileDomainId (0) gsmNetworkId(1)
   moduleId (3) map-CommonDataTypes (18) version2 (2)}
;


SendRoutingInfoForSM ::= OPERATION				--Timer m--
	ARGUMENT
		routingInfoForSM-Arg	RoutingInfoForSM-Arg
	RESULT
		routingInfoForSM-Res	RoutingInfoForSM-Res
	ERRORS {
		SystemFailure,
		DataMissing,
		UnexpectedDataValue,
		FacilityNotSupported,
		UnknownSubscriber,
		TeleserviceNotProvisioned,
		AbsentSubscriber,
		CallBarred}

ForwardSM ::= OPERATION					--Timer m--
	ARGUMENT
		forwardSM-Arg	ForwardSM-Arg
	RESULT zzzz-Empty	NULL
	ERRORS {
		SystemFailure,
		DataMissing,
		-- NU1 DataMissing must not be used in version 1
		UnexpectedDataValue,
		FacilityNotSupported,
		UnidentifiedSubscriber,
		IllegalSubscriber,
		IllegalEquipment,
		-- NU1 IllegalEquipment must not be used in version 1
		AbsentSubscriber,
		SM-DeliveryFailure}

ReportSM-DeliveryStatus ::= OPERATION			--Timer s--
	ARGUMENT
		reportSM-DeliveryStatusArg	ReportSM-DeliveryStatusArg
	RESULT
		storedMSISDN	ISDN-AddressString
		-- optional
		-- OA1 storedMSISDN must be absent in version 1
		-- OP>1 storedMSISDN must be present in version greater 1
	ERRORS {
		DataMissing,
		-- NU1 DataMissing must not be used in version 1
		UnexpectedDataValue,
		UnknownSubscriber,
		MessageWaitingListFull}

NoteSubscriberPresent ::= OPERATION				--Timer s--
	ARGUMENT
		imsi		IMSI

AlertServiceCentre ::= OPERATION				--Timer s--
	ARGUMENT
		alertServiceCentreArg	AlertServiceCentreArg
	RESULT zzzz-Empty	NULL
		-- OA1 RESULT must be absent in version 1
		-- OU>1 RESULT must be used in version greater 1
	ERRORS {
		SystemFailure,
		-- NU1 SystemFailure must not be used in version 1
		DataMissing,
		-- NU1 DataMissing must not be used in version 1
		UnexpectedDataValue}
		-- NU1 UnexpectedDataValue must not be used in version 1

InformServiceCentre ::= OPERATION				--Timer s--
	ARGUMENT
		informServiceCentreArg	InformServiceCentreArg

SendInfoForMT-SMS ::= OPERATION				--Timer s--
	ARGUMENT
		sm-RP-DA	SM-RP-DA
	RESULT
		msisdn	ISDN-AddressString
	ERRORS {
		SystemFailure,
		DataMissing,
		UnexpectedDataValue,
		UnknownSubscriber,
		UnidentifiedSubscriber,
		IllegalSubscriber,
		IllegalEquipment,
		AbsentSubscriber}

SendInfoForMO-SMS ::= OPERATION				--Timer s--
	ARGUMENT
		serviceCentreAddress	AddressString
	RESULT
		msisdn	ISDN-AddressString
	ERRORS {
		DataMissing,
		UnexpectedDataValue,
		TeleserviceNotProvisioned,
		CallBarred}

ReadyForSM ::= OPERATION				--Timer m--
	ARGUMENT
		readyForSM-Arg	ReadyForSM-Arg
	RESULT zzzz-Empty	NULL
	ERRORS {
		DataMissing,
		UnexpectedDataValue,
		UnknownSubscriber}


END
-- MODULE END
